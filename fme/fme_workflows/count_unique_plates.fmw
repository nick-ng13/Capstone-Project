FME workspace count_unique_plates.fmw

Parameters:
- SourceDataset_MSSQL_ADO = autoVu   # SQL Server Connection
- DestDataset_XLSXW = C:\!Capstone\autovu_reads.xlsx   # Destination Microsoft Excel File
- SourceDataset_MSSQL_ADO_5 = autoVu   # SQL Server Connection
- SourceDataset_MSSQL_ADO_7 = autoVu   # SQL Server Connection
- SourceDataset_MSSQL_ADO_6 = autoVu   # SQL Server Connection

Readers:
- MSSQL_ADO_1: MSSQL_ADO from $(SourceDataset_MSSQL_ADO)
- MSSQL_ADO_2: MSSQL_ADO from $(SourceDataset_MSSQL_ADO_5)
- MSSQL_ADO_3: MSSQL_ADO from $(SourceDataset_MSSQL_ADO_7)
- MSSQL_ADO_4: MSSQL_ADO from $(SourceDataset_MSSQL_ADO_6)

Writers:
- XLSXW_1: XLSXW to $(DestDataset_XLSXW)

PythonCaller
    PYTHONSOURCE:
      import fme
      import fmeobjects


      class FeatureProcessor(object):
          """Template Class Interface:
          When using this class, make sure its name is set as the value of the 'Class
          to Process Features' transformer parameter.
          """

          def __init__(self):
              """Base constructor for class members."""
              print(self.__dict__)
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              print("In input")
              print(f"{feature=}")
              print(self.pyoutput(feature))


          def close(self):
              """This method is called once all the FME Features have been processed
              from input().
              """
              print("In close")
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              print("In process group")
              return 45

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              print("In has support for")
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
Reads (reader MSSQL_ADO_1)
    attributes: Id bigint, ReadId uniqueidentifier, Plate nvarchar(12), PlateState nvarchar(10), Longitude float, Latitude float, IsHit bit, IsEdited bit, UnitId uniqueidentifier, DeviceId uniqueidentifier, Street nvarchar(255), CivicNumber integer, ProcessedFlag integer, Attributes xml, Watermark varbinary(40), TimestampLocal datetime2, TimestampUtc datetime2, TimestampTimeZone varchar(64), TimestampImportedLocal datetime2, TimestampImportedUtc datetime2, ProtectedUntilUtc datetime2, ImageMetadata varbinary(1024), UnitHeading float, UnitSpeed float, IsManualCapture bit, UserId uniqueidentifier, PatrollerId uniqueidentifier, PermitId uniqueidentifier, RuleId uniqueidentifier, LotId uniqueidentifier,
      InventoryIndex integer, TimeSpanParked integer, ImagesWatermark varbinary(40)
    -> AttributeManager
AttributeManager
    ATTR_TABLE:
      REMOVE Id
      REMOVE ReadId
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> StatisticsCalculator
    -> raw_output (writer XLSXW_1)
StatisticsCalculator
    CALCULATION_MODE = PER_ATTR
    FEAT_STATS = Plate,LEXICAL,,,COUNT,<Unused>,<Unused>,,,,<Unused>,<Unused>,<Unused>,,
    GROUP_BY = Plate
    SUMMARY -> hello (writer XLSXW_1)
hello (writer XLSXW_1)
    attributes: Plate string(12), Plate.total_count number(20)
raw_output (writer XLSXW_1)
    attributes: Plate string(12), TimestampLocal datetime(20)
Reads (reader MSSQL_ADO_2)
    attributes: Id bigint, ReadId uniqueidentifier, Plate nvarchar(12), PlateState nvarchar(10), Longitude float, Latitude float, IsHit bit, IsEdited bit, UnitId uniqueidentifier, DeviceId uniqueidentifier, Street nvarchar(255), CivicNumber integer, ProcessedFlag integer, Attributes xml, Watermark varbinary(40), TimestampLocal datetime2, TimestampUtc datetime2, TimestampTimeZone varchar(64), TimestampImportedLocal datetime2, TimestampImportedUtc datetime2, ProtectedUntilUtc datetime2, ImageMetadata varbinary(1024), UnitHeading float, UnitSpeed float, IsManualCapture bit, UserId uniqueidentifier, PatrollerId uniqueidentifier, PermitId uniqueidentifier, RuleId uniqueidentifier, LotId uniqueidentifier,
      InventoryIndex integer, TimeSpanParked integer, ImagesWatermark varbinary(40)
    -> AttributeManager_2
    -> get_entrance_time
    -> get_exit_time_2
AttributeManager_2
    ATTR_TABLE:
      REMOVE Id
      REMOVE ReadId
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> DateTimeConverter
DateTimeConverter
    DATETIME_ATTR = TimestampLocal
    OUT_FORMAT = %Y%m%d
    PASSTHROUGH = NO
    REPAIR_INPUT = YES
    -> StatisticsCalculator_2
StatisticsCalculator_2
    CALCULATION_MODE = PER_ATTR
    FEAT_STATS = Plate,LEXICAL,,,COUNT,<Unused>,<Unused>,,,,<Unused>,<Unused>,<Unused>,,
    GROUP_BY = Plate TimestampLocal
    SUMMARY -> StatisticsCalculator_3
StatisticsCalculator_3
    CALCULATION_MODE = PER_ATTR
    FEAT_STATS = TimestampLocal,NUMERIC_MODE,,,COUNT,,,,,,,,,,
    GROUP_BY = TimestampLocal
    SUMMARY -> 2023 (writer XLSXW_1)
2023 (writer XLSXW_1)
    attributes: TimestampLocal datetime(20), TimestampLocal.total_count number(20)
get_entrance_time: AttributeManager
    ATTR_TABLE:
      REMOVE Id
      REMOVE ReadId
      RENAME_SET_VALUE Plate > license_plate
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      RENAME_SET_VALUE TimestampLocal > entrance_time
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> 2023_new (writer XLSXW_1)
    -> FeatureMerger [REQUESTOR]
    -> Aggregator
    -> ListBuilder_2
2023_new (writer XLSXW_1)
    attributes: license_plate string(12), entrance_time datetime(20)
ListBuilder_2
    LIST_NAME = _list
    -> ListSorter_3
ListSorter_3
    ORDER = Ascending
    SRC_LIST = _list{}.entrance_time
    TYPE = Alphabetic
    -> ListExploder_4
ListExploder_4
    ATTR_ACCUM_MODE = Merge List Attributes
    ATTR_CONFLICT_RES = Use List Attribute Values
    INDEX_ATTR = _element_index
    LIST_ATTR = _list{}
    ELEMENTS -> FeatureMerger_2 [REQUESTOR]
    ELEMENTS -> PLEASE MAN TEST00 (writer XLSXW_1)
    <REJECTED> -> filter_rejection
Reads (reader MSSQL_ADO_4)
    attributes: Id bigint, ReadId uniqueidentifier, Plate nvarchar(12), PlateState nvarchar(10), Longitude float, Latitude float, IsHit bit, IsEdited bit, UnitId uniqueidentifier, DeviceId uniqueidentifier, Street nvarchar(255), CivicNumber integer, ProcessedFlag integer, Attributes xml, Watermark varbinary(40), TimestampLocal datetime2, TimestampUtc datetime2, TimestampTimeZone varchar(64), TimestampImportedLocal datetime2, TimestampImportedUtc datetime2, ProtectedUntilUtc datetime2, ImageMetadata varbinary(1024), UnitHeading float, UnitSpeed float, IsManualCapture bit, UserId uniqueidentifier, PatrollerId uniqueidentifier, PermitId uniqueidentifier, RuleId uniqueidentifier, LotId uniqueidentifier,
      InventoryIndex integer, TimeSpanParked integer, ImagesWatermark varbinary(40)
    -> get_exit_time
    -> get_exit_time_2
get_exit_time: AttributeManager
    ATTR_TABLE:
      REMOVE Id
      REMOVE ReadId
      RENAME_SET_VALUE Plate > license_plate
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      RENAME_SET_VALUE TimestampLocal > exit_time
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> FeatureMerger [SUPPLIER]
    -> Aggregator
    -> ListBuilder_3
Aggregator
    ACCUM_ATTRS_NAME = Drop Incoming Attributes
    AGGREGATE_TYPE = Homogeneous Collection (If Possible)
    GROUP_BY = license_plate entrance_time exit_time
    LIST_NAME = mylist
    MODE = Geometry - Assemble One Level
    SEP = ,
    AGGREGATE -> ListSorter
ListSorter
    ORDER = Ascending
    SRC_LIST = mylist{}.license_plate
    TYPE = Alphabetic
    -> 2023_merged_reverse (writer XLSXW_1)
2023_merged_reverse (writer XLSXW_1)
    attributes: license_plate string(12), entrance_time datetime(20), exit_time datetime(20), mylist{}.license_plate string(12), mylist{}.entrance_time datetime(20), mylist{}.exit_time datetime(20)
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(license_plate) @Value(license_plate) STRING
    LIST_NAME = mylist
    MERGE_TYPE = Attributes Only
    PROCESS_DUPS = YES
    REJECT_NULL_MISSING_KEYS = No
    SUPPLIERS_FIRST = No
    MERGED -> ListExploder
    <REJECTED> -> filter_rejection
ListExploder
    ATTR_ACCUM_MODE = Merge List Attributes
    ATTR_CONFLICT_RES = Use List Attribute Values
    INDEX_ATTR = _element_index
    LIST_ATTR = mylist{}
ListBuilder_3
    LIST_NAME = _list
    -> ListSorter_4
ListSorter_4
    ORDER = Ascending
    SRC_LIST = _list{}.exit_time
    TYPE = Alphabetic
    -> ListExploder_5
ListExploder_5
    ATTR_ACCUM_MODE = Merge List Attributes
    ATTR_CONFLICT_RES = Use List Attribute Values
    INDEX_ATTR = _element_index
    LIST_ATTR = _list{}
    ELEMENTS -> FeatureMerger_2 [SUPPLIER]
    ELEMENTS -> PLEASE MAN TEST00 (writer XLSXW_1)
    <REJECTED> -> filter_rejection
PLEASE MAN TEST00 (writer XLSXW_1)
    attributes: license_plate string(12), entrance_time datetime(20), _element_index number(20), exit_time datetime(20)
FeatureMerger_2
    ATTR_ACCUM_MODE = Merge Supplier
    ATTR_CONFLICT_RES = Use Requestor
    GROUP_BY = license_plate
    IGNORE_NULLS = No
    JOIN_KEYS = 1 1 AUTO
    MERGE_TYPE = Attributes Only
    PROCESS_DUPS = NO
    REJECT_NULL_MISSING_KEYS = No
    SUPPLIERS_FIRST = No
    MERGED -> ListBuilder
    MERGED -> PLEASE MAN TEST (writer XLSXW_1)
    <REJECTED> -> filter_rejection
PLEASE MAN TEST (writer XLSXW_1)
    attributes: license_plate string(12), entrance_time datetime(20), _element_index number(20), exit_time datetime(20)
ListBuilder
    LIST_NAME = _list
    -> ListSorter_2
ListSorter_2
    ORDER = Ascending
    SRC_LIST = _list{}.exit_time
    TYPE = Alphabetic
    -> ListExploder_3
ListExploder_3
    ATTR_ACCUM_MODE = Merge List Attributes
    ATTR_CONFLICT_RES = Use List Attribute Values
    LIST_ATTR = _list{}
    ELEMENTS -> DateTimeCalculator
    <REJECTED> -> filter_rejection
DateTimeCalculator
    MODE = DATETIMECALC_3_CALCULATE_INTERVAL
    OPERATION_PARAMETERS = START_DATETIME]@Value(entrance_time)]END_DATETIME]@Value(exit_time)]RESULT_TYPE]HOURS]RESULT_INTERVAL]_result_interval]FME_CONTROLLER_QUERY_FILE]transformers/dependencies/datetimecalculator/DATETIMECALC_3_CALCULATE_INTERVAL.fme]FME_CONTROLLER_CHOICE]DATETIMECALC_3_CALCULATE_INTERVAL
    -> PLEASE MAN (writer XLSXW_1)
    <REJECTED> -> filter_rejection
PLEASE MAN (writer XLSXW_1)
    attributes: license_plate string(12), entrance_time datetime(20), _element_index number(20), exit_time datetime(20), _result_interval string(200)
filter_rejection: AttributeManager
    ATTR_TABLE = REMOVE fme_rejection_code
get_exit_time_2: AttributeManager
    ATTR_TABLE:
      REMOVE Id
      REMOVE ReadId
      RENAME_SET_VALUE Plate > license_plate
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      RENAME_SET_VALUE TimestampLocal > time
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> ListExploder_2
ListExploder_2
    ATTR_ACCUM_MODE = Merge List Attributes
    ATTR_CONFLICT_RES = Use List Attribute Values
    INDEX_ATTR = _element_index
    LIST_ATTR = mylist{}
    ELEMENTS -> 2023_dumb (writer XLSXW_1)
2023_dumb (writer XLSXW_1)
    attributes: license_plate string(12), time datetime(20), _element_index number(20)
