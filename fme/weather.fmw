FME workspace weather.fmw

Parameters:
- DestDataset_XLSXW = C:\Users\mason\Desktop\weather.xlsx   # Destination Microsoft Excel File
- DestDataset_XLSXW_5 = C:\Users\mason\Desktop\weather.xlsx   # Destination Microsoft Excel File
- DestDataset_XLSXW_4 = C:\Users\mason\Desktop\weather.xlsx   # Destination Microsoft Excel File

Writers:
- XLSXW_1: XLSXW to $(DestDataset_XLSXW)
- XLSXW_2: XLSXW to $(DestDataset_XLSXW_5)
- XLSXW_3: XLSXW to $(DestDataset_XLSXW_4)

Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = http://api.weatherapi.com/v1/current.json?key=2000a77f324d4ba2919224706220111&q=Vancouver&aqi=no
    TRANSFER_TIMEOUT_LENGTH = 90
    USE_COOKIES = No
    VERIFY_SSL_CERTIFICATES = Yes
    -> JSONFragmenter_location
    -> JSONFragmenter_current
    -> JSONFragmenter
JSONFragmenter_location
    EXPLODE_FORMAT = JSON
    EXTRACT_ATTR = Yes
    JSON_ATTR = _response_body
    JSON_QUERY = json["location"][*]
    READ_FROM_FILE = NO
    RECURSIVE = Yes
    REJECT_EMPTY_LISTS = YES
    FRAGMENTS -> AttributeManager
AttributeManager
    -> Sheet1 (writer XLSXW_1)
Sheet1 (writer XLSXW_1)
    attributes: _creation_instance number(20), _response_body string(20), _http_status_code string(20), json_type string(20), json_index number(20)
JSONFragmenter_current
    EXPLODE_FORMAT = JSON
    EXTRACT_ATTR = Yes
    JSON_ATTR = _response_body
    JSON_QUERY = json["current"][*]
    READ_FROM_FILE = NO
    RECURSIVE = Yes
    REJECT_EMPTY_LISTS = YES
    FRAGMENTS -> current (writer XLSXW_3)
current (writer XLSXW_3)
    attributes: _creation_instance number(20), _response_body string(20), _http_status_code string(20), json_type string(20), json_index number(20)
JSONFragmenter
    EXPLODE_FORMAT = JSON
    EXTRACT_ATTR = No
    JSON_ATTR = _response_body
    JSON_QUERY = json[*]
    READ_FROM_FILE = NO
    REJECT_EMPTY_LISTS = YES
    FRAGMENTS -> Sheet2 (writer XLSXW_2)
Sheet2 (writer XLSXW_2)
    attributes: _creation_instance number(20), _response_body string(20), _http_status_code string(20), json_type string(20), json_index number(20)
