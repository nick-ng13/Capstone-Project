FME workspace count_unique_plates.fmw

Parameters:
- SourceDataset_MSSQL_ADO = AutoVu   # SQL Server Connection
- DestDataset_XLSXW = C:\!Capstone\autovu_reads.xlsx   # Destination Microsoft Excel File
- SourceDataset_MSSQL_ADO_5 = LPRManager   # SQL Server Connection
- DestDataset_XLSXW_9 = $(FME_MF_DIR)output.xlsx   # Destination Microsoft Excel File
- SourceDataset_MSSQL_ADO_7 = LPRManager   # SQL Server Connection
- SourceDataset_XLSXR = $(FME_MF_DIR)LPR_Cameras_2022.xlsx   # Source Microsoft Excel File(s)
- DestDataset_XLSXW_6 = C:\!Capstone\jerry_data1.xlsx   # Destination Microsoft Excel File
- DestDataset_XLSXW_8 = C:\!Capstone\jerry_data.xlsx   # Destination Microsoft Excel File
- DestDataset_MSSQL_ADO = result   # SQL Server Connection
- SourceDataset_XLSXR_3 = C:\!Capstone\ParkingIds.xlsx   # Source Microsoft Excel File(s)

Readers:
- MSSQL_ADO_1: MSSQL_ADO from $(SourceDataset_MSSQL_ADO)
- MSSQL_ADO_2: MSSQL_ADO from $(SourceDataset_MSSQL_ADO_5)
- MSSQL_ADO_3: MSSQL_ADO from $(SourceDataset_MSSQL_ADO_7)
- XLSXR_2: XLSXR from $(SourceDataset_XLSXR)
- XLSXR_1: XLSXR from $(SourceDataset_XLSXR_3)

Writers:
- XLSXW_1: XLSXW to $(DestDataset_XLSXW)
- XLSXW_2: XLSXW to $(DestDataset_XLSXW_9)
- XLSXW_4: XLSXW to $(DestDataset_XLSXW_6)
- XLSXW_5: XLSXW to $(DestDataset_XLSXW_8)
- MSSQL_ADO_4: MSSQL_ADO to $(DestDataset_MSSQL_ADO)

Reads (reader MSSQL_ADO_3)
    attributes: Id bigint, ReadId uniqueidentifier, Plate nvarchar(12), PlateState nvarchar(10), Longitude float, Latitude float, IsHit bit, IsEdited bit, UnitId uniqueidentifier, DeviceId uniqueidentifier, Street nvarchar(255), CivicNumber integer, ProcessedFlag integer, Attributes xml, Watermark varbinary(40), TimestampLocal datetime2, TimestampUtc datetime2, TimestampTimeZone varchar(64), TimestampImportedLocal datetime2, TimestampImportedUtc datetime2, ProtectedUntilUtc datetime2, ImageMetadata varbinary(1024), UnitHeading float, UnitSpeed float, IsManualCapture bit, UserId uniqueidentifier, PatrollerId uniqueidentifier, PermitId uniqueidentifier, RuleId uniqueidentifier, LotId uniqueidentifier,
      InventoryIndex integer, TimeSpanParked integer, ImagesWatermark varbinary(40)
    -> AttributeManager_3
AttributeManager_3
    ATTR_TABLE:
      REMOVE Id
      REMOVE ReadId
      RENAME_SET_VALUE Plate > licence_plate
      REMOVE PlateState
      REMOVE Longitude
      REMOVE Latitude
      REMOVE IsHit
      REMOVE IsEdited
      REMOVE UnitId
      RENAME_SET_VALUE DeviceId > camera_id
      REMOVE Street
      REMOVE CivicNumber
      REMOVE ProcessedFlag
      REMOVE Attributes
      REMOVE Watermark
      RENAME_SET_VALUE TimestampLocal > time
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> FeatureJoiner [LEFT]
Parkades (reader XLSXR_2)
    attributes: camera_id char(37), type char(6)
Thunderbird (reader XLSXR_1)
    attributes: camera_id char(37), type char(6)
    -> FeatureJoiner [RIGHT]
Note: merge enter/exit
FeatureJoiner
    ATTR_CONFLICT_RES = Prefer Left
    GEOMETRY_HANDLING = Prefer Left
    JOIN_KEYS = camera_id camera_id AUTO
    JOIN_MODE = Inner
    JOINED -> Sorter_2
Sorter_2
    GROUP_BY = licence_plate
    SORT_PARM = time NUMERIC ASCENDING
    SORTED -> AttributeCreator_2
    SORTED -> IR (writer XLSXW_2)
IR (writer XLSXW_2)
    attributes: licence_plate string(12), camera_id string(20), time datetime(20), type string(6)
Note: conditionals for from/to time - using adjacent attributes / This 'merges' the enter/exit times
AttributeCreator_2
    ATTR_TABLE:
      SET_TO fromTime = FME_CONDITIONAL:DEFAULT_VALUE'_FME_NO_OP_'BOOL_OP;OR;COMPOSITE_TEST;1;TEST @Value(type) = enter'@Value(time)'FME_NUM_CONDITIONS2___
      SET_TO toTime = FME_CONDITIONAL:DEFAULT_VALUE'_FME_NO_OP_'BOOL_OP;OR;COMPOSITE_TEST;1;TEST @Value(feature[+1].type) = exit'@Value(feature[+1].time)'FME_NUM_CONDITIONS2___
    NUM_PRIOR_FEATURES = 0
    NUM_SUBSEQUENT_FEATURES = 1
    -> TestFilter
Note: drop the exit records
TestFilter
    DEFAULT_VALUE = <UNFILTERED>
    PASSED_TEST_GROUP_OUTPUT = FIRST
    TEST_LIST = "BOOL_OP,OR,COMPOSITE_TEST,""""""1"""""",TEST_CLAUSE,TEST @Value(type) = enter",keep
    keep -> Sorter
Sorter
    SORT_PARM = fromTime NUMERIC ASCENDING
    SORTED -> parkingDurations (writer MSSQL_ADO_4)
    SORTED -> our_results (writer XLSXW_2)
parkingDurations (writer MSSQL_ADO_4)
    attributes: fromTime varchar(200), toTime varchar(200), licence_plate nvarchar(12), camera_id uniqueidentifier, time datetime2, type varchar(6)
our_results (writer XLSXW_2)
    attributes: fromTime string(200), toTime string(200), licence_plate string(12), camera_id string(20), time datetime(20), type string(6)
Reads (reader MSSQL_ADO_2)
    attributes: Id bigint, ReadId uniqueidentifier, Plate nvarchar(12), PlateState nvarchar(10), Longitude float, Latitude float, IsHit bit, IsEdited bit, UnitId uniqueidentifier, DeviceId uniqueidentifier, Street nvarchar(255), CivicNumber integer, ProcessedFlag integer, Attributes xml, Watermark varbinary(40), TimestampLocal datetime2, TimestampUtc datetime2, TimestampTimeZone varchar(64), TimestampImportedLocal datetime2, TimestampImportedUtc datetime2, ProtectedUntilUtc datetime2, ImageMetadata varbinary(1024), UnitHeading float, UnitSpeed float, IsManualCapture bit, UserId uniqueidentifier, PatrollerId uniqueidentifier, PermitId uniqueidentifier, RuleId uniqueidentifier, LotId uniqueidentifier,
      InventoryIndex integer, TimeSpanParked integer, ImagesWatermark varbinary(40)
    -> AttributeManager_2
AttributeManager_2
    ATTR_TABLE:
      REMOVE Id
      REMOVE ReadId
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> DateTimeConverter
DateTimeConverter
    DATETIME_ATTR = TimestampLocal
    OUT_FORMAT = %Y%m%d
    PASSTHROUGH = NO
    REPAIR_INPUT = YES
    -> StatisticsCalculator_2
StatisticsCalculator_2
    CALCULATION_MODE = PER_ATTR
    FEAT_STATS = Plate,LEXICAL,,,COUNT,<Unused>,<Unused>,,,,<Unused>,<Unused>,<Unused>,,
    GROUP_BY = Plate TimestampLocal
    SUMMARY -> StatisticsCalculator_3
StatisticsCalculator_3
    CALCULATION_MODE = PER_ATTR
    FEAT_STATS = TimestampLocal,NUMERIC_MODE,,,COUNT,,,,,,,,,,
    GROUP_BY = TimestampLocal
    SUMMARY -> 3years (writer XLSXW_4)
    SUMMARY -> jerry (writer XLSXW_1)
jerry (writer XLSXW_1)
    attributes: TimestampLocal datetime(20), TimestampLocal.total_count number(20)
3years (writer XLSXW_4)
Reads (reader MSSQL_ADO_1)
    attributes: Id bigint, ReadId uniqueidentifier, Plate nvarchar(12), PlateState nvarchar(10), Longitude float, Latitude float, IsHit bit, IsEdited bit, UnitId uniqueidentifier, DeviceId uniqueidentifier, Street nvarchar(255), CivicNumber integer, ProcessedFlag integer, Attributes xml, Watermark varbinary(40), TimestampLocal datetime2, TimestampUtc datetime2, TimestampTimeZone varchar(64), TimestampImportedLocal datetime2, TimestampImportedUtc datetime2, ProtectedUntilUtc datetime2, ImageMetadata varbinary(1024), UnitHeading float, UnitSpeed float, IsManualCapture bit, UserId uniqueidentifier, PatrollerId uniqueidentifier, PermitId uniqueidentifier, RuleId uniqueidentifier, LotId uniqueidentifier,
      InventoryIndex integer, TimeSpanParked integer, ImagesWatermark varbinary(40)
    -> AttributeManager
AttributeManager
    ATTR_TABLE:
      REMOVE Id
      REMOVE ReadId
      REMOVE PlateState
      REMOVE Longitude
      REMOVE Latitude
      REMOVE IsHit
      REMOVE IsEdited
      REMOVE UnitId
      REMOVE DeviceId
      REMOVE Street
      REMOVE CivicNumber
      REMOVE ProcessedFlag
      REMOVE Attributes
      REMOVE Watermark
      REMOVE TimestampUtc
      REMOVE TimestampTimeZone
      REMOVE TimestampImportedLocal
      REMOVE TimestampImportedUtc
      REMOVE ProtectedUntilUtc
      REMOVE ImageMetadata
      REMOVE UnitHeading
      REMOVE UnitSpeed
      REMOVE IsManualCapture
      REMOVE UserId
      REMOVE PatrollerId
      REMOVE PermitId
      REMOVE RuleId
      REMOVE LotId
      REMOVE InventoryIndex
      REMOVE TimeSpanParked
      REMOVE ImagesWatermark
    -> StatisticsCalculator
    -> raw_output (writer XLSXW_1)
StatisticsCalculator
    CALCULATION_MODE = PER_ATTR
    FEAT_STATS = Plate,LEXICAL,,,COUNT,<Unused>,<Unused>,,,,<Unused>,<Unused>,<Unused>,,
    GROUP_BY = Plate
    SUMMARY -> hello (writer XLSXW_1)
hello (writer XLSXW_1)
    attributes: Plate string(12), Plate.total_count number(20)
raw_output (writer XLSXW_1)
    attributes: Plate string(12), TimestampLocal datetime(20)
